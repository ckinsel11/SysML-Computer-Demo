package 'Template Trade Study'{
    private import TradeStudies::*;

    analysis 'Template Trade Study' : TradeStudy {
        doc /* This is a template for a trade study. It provides a structured approach to evaluating alternatives based on specified criteria and objectives. */

        /* Step 1: Identify requirements and assumptions */

        /* Step 2: Identify alternatives under consideration */
            /* Create usages for each alternative assuming the alternatives are individual components. */
            /*part PART1 : TYPE */
            /*part PART2 : TYPE */
            /*part PART3 : TYPE */
        /*subject ALT = (PART1, PART2, PART3);*/

        /* Step 3: Identify evaluation criteria */

        /* Step 4: Weight selection criteria */
            /* Set the objective of the evaluation function. The function should either maximize or minimize the value. */
        objective : MaximizeObjective; 

        /* Step 5: Define criteria scoring scale */

        /* Step 6: Conduct evaluation of alternatives */

        /* Step 7: Record results */
    }
}
