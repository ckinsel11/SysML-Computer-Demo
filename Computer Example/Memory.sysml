package Memory {
    private import ScalarValues::*;


    part def Memory {
        doc /*  */
        attribute 'First Word Latency' : Real;
        attribute 'CAS Latency' : Real;
        attribute Speed;
        attribute 'Number of Modules' : Integer;
        attribute 'Module Size' : Real;
    }
}
