package 'Video Card' {
    part def 'Video Card' {
        attribute Chipset;
        attribute Memory : Real;
        attribute 'Core Clock' : Real;
        attribute 'Boost Clock' : Real;
        attribute Length : Real;
    }
}
