package Mouse {
    abstract part def Mouse {
        doc /* A computer mouse is a hand-held pointing device that detects two-dimensional motion relative to a surface. */

        port 'PC Connector';
        port LMB;
        port RMB;
        port 'Scroll Wheel'; 
        port Sensor;
    }
}
