library package 'Connector Library'{
    package HDMI {
        port def 'Type A' {
            doc /*  */
        }
    }
    package USB {
        port def 'Standard-A'{
            doc /*  */
        }
        port def 'Standard-B'{
            doc /*  */
        }
        port def 'Mini-A'{
            doc /*  */
        }
        port def 'Mini-AB'{
            doc /*  */
        }
        port def 'Mini-B'{
            doc /*  */
        }
        port def 'Micro-A'{
            doc /*  */
        }
        port def 'Micro-AB'{
            doc /*  */
        }
        port def 'Micro-B'{
            doc /*  */
        }
        port def 'Type-C'{
            doc /*  */
        }
    }
}
