package 'Contact Arrangements' {
    package 'USB'{
        port def 'USB Type A' {
            port '1';
            port '2';
            port '3';
            port '4';
        }
        port def 'USB Type A SuperSpeed' :> 'USB Type A' {
            port '5';
            port '6';
            port '7';
            port '8';
            port '9';
        }
        port def 'USB Type B' {
            port '1';
            port '2';
            port '3';
            port '4';
        }
        port def 'USB Type B SuperSpeed' :> 'USB Type B' {
            port '5';
            port '6';
            port '7';
            port '8';
            port '9';
        }
        port def 'Mini-A' {
            port '1';
            port '2';
            port '3';
            port '4';
            port '5';
        }
        port def 'Mini-AB' {
            port '1';
            port '2';
            port '3';
            port '4';
            port '5';
        }
        port def 'Mini-B' {
            port '1';
            port '2';
            port '3';
            port '4';
            port '5';
        }
        port def 'Micro-A' {
            port '1';
            port '2';
            port '3';
            port '4';
            port '5';
        }
        port def 'Micro-A SuperSpeed' :> 'Micro-A' {
            port '6';
            port '7';
            port '8';
            port '9';
            port '10';
        }
        port def 'Micro-AB' {
            port '1';
            port '2';
            port '3';
            port '4';
            port '5';
        }
        port def 'Micro-AB SuperSpeed' :> 'Micro-AB' {
            port '6';
            port '7';
            port '8';
            port '9';
            port '10';
        }
        port def 'Micro-B' {
            port '1';
            port '2';
            port '3';
            port '4';
            port '5';
        }
    }
}
